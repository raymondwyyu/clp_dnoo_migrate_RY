FME workspace Closed_StructBoundary_v0.1.fmw

Parameters:
- DestDataset_GEODATABASE_FILE = E:\Temp\RY\Test_RY1\Test_RY1c.gdb   # File Geodatabase
- SourceDataset_ORACLE_SPATIAL = dnoo   # Connection
- DestDataset_CSV2 = E:\Temp\RY\Test_RY1   # Destination CSV (Comma Separated Value) Folder

Readers:
- ORACLE_SPATIAL_1: ORACLE_SPATIAL from $(SourceDataset_ORACLE_SPATIAL) in HongKong80b.GridSystem

Writers:
- GEODATABASE_FILE_2: GEODATABASE_FILE to $(DestDataset_GEODATABASE_FILE)
- CSV2_1: CSV2 to $(DestDataset_CSV2)

DNOO_SH_TROUGH (reader ORACLE_SPATIAL_1)
    attributes: GLOBALID varchar2(38), BOUNDARYID number(22,0), CUSTTYPE number(22,0), DATE_LASTUPD date, DATE_TARGETEND date, DATE_TARGETSTART date, DEPT varchar2(3), G3E_FID number(10,0), G3E_FNO number(5,0), G3E_ID number(10,0), IPID number(22,0), JOBMODIFIED varchar2(30), JOBPLACED varchar2(30), LASTUPDBY varchar2(20), LOCALNUM varchar2(6), MAPNAME varchar2(8), METERNUM number(22,0), OC varchar2(2), OWNERCNO number(5,0), OWNID number(22,0), PREMISNUM varchar2(12), PROJSCH varchar2(12), RB_STATE number(22,0), REMARKS varchar2(30), SAPDESCRIPTION varchar2(40), SAP_EQUIP_ID varchar2(18), SAP_FUN_LOC_ID varchar2(40), SAP_NULL_DATE date, SAP_POST_ID varchar2(50), SEROWNID number(22,0),
      STATUS number(22,0), VOLTAGE varchar2(3), DATE_COMM_D date, DEPTH1 number, DEPTH2 number, MATERIAL varchar2(8), NONSTDDEPTH varchar2(1), TYPE varchar2(16), TEXT varchar2(1023), CONVERSION_REMARKS varchar2(4000)
    -> AreaBuilder
AreaBuilder
    ALLOW_CYCLES = No
    CHECK_CURVE_DIRECTION = No
    CONNECT_Z_MODE = First Wins
    CONSIDER_NODE_ELEVATION = no
    DEAGGREGATE_INPUT = Deaggregate
    DONUT_CREATION = Yes
    DROP_HOLES = No
    LINES_AS_SEGMENTS = No
    POLY_ACCUM_ATTRS_NAME = Use Attributes From One Feature
    SNAPTYPE_PARAM = None
    AREA -> DNOO_SH_TROUGH_POLY (writer GEODATABASE_FILE_2)
    Incomplete -> LineCloser
    <REJECTED> -> closed_structboundary_err (writer CSV2_1)
LineCloser
    CONNECT_Z_MODE = First Wins
    AREA -> DNOO_SH_TROUGH_POLY (writer GEODATABASE_FILE_2)
DNOO_SH_TROUGH_POLY (writer GEODATABASE_FILE_2)
    attributes: GLOBALID char(38), BOUNDARYID double(22,0), CUSTTYPE double(22,0), DATE_LASTUPD date, DATE_TARGETEND date, DATE_TARGETSTART date, DEPT char(3), G3E_FID double(10,0), G3E_FNO integer, G3E_ID double(10,0), IPID double(22,0), JOBMODIFIED char(30), JOBPLACED char(30), LASTUPDBY char(20), LOCALNUM char(6), MAPNAME char(8), METERNUM double(22,0), OC char(2), OWNERCNO integer, OWNID double(22,0), PREMISNUM char(12), PROJSCH char(12), RB_STATE double(22,0), REMARKS char(30), SAPDESCRIPTION char(40), SAP_EQUIP_ID char(18), SAP_FUN_LOC_ID char(40), SAP_NULL_DATE date, SAP_POST_ID char(50), SEROWNID double(22,0),
      STATUS double(22,0), VOLTAGE char(3), DATE_COMM_D date, DEPTH1 double, DEPTH2 double, MATERIAL char(8), NONSTDDEPTH char(1), TYPE char(16), TEXT char(1023), CONVERSION_REMARKS char(4000)
DNOO_SH_SHALL (reader ORACLE_SPATIAL_1)
    attributes: GLOBALID varchar2(38), BOUNDARYID number(22,0), CUSTTYPE number(22,0), DATE_LASTUPD date, DATE_TARGETEND date, DATE_TARGETSTART date, DEPT varchar2(3), G3E_FID number(10,0), G3E_FNO number(5,0), G3E_ID number(10,0), IPID number(22,0), JOBMODIFIED varchar2(30), JOBPLACED varchar2(30), LASTUPDBY varchar2(20), LOCALNUM varchar2(6), MAPNAME varchar2(8), METERNUM number(22,0), OC varchar2(2), OWNERCNO number(5,0), OWNID number(22,0), PREMISNUM varchar2(12), PROJSCH varchar2(12), RB_STATE number(22,0), REMARKS varchar2(30), SAPDESCRIPTION varchar2(40), SAP_EQUIP_ID varchar2(18), SAP_FUN_LOC_ID varchar2(40), SAP_NULL_DATE date, SAP_POST_ID varchar2(50), SEROWNID number(22,0),
      STATUS number(22,0), VOLTAGE varchar2(3), TEXT varchar2(1023), SHSHALLOW_REMARK varchar2(32), CONVERSION_REMARKS varchar2(4000)
    -> AreaBuilder_2
AreaBuilder_2
    ALLOW_CYCLES = No
    CHECK_CURVE_DIRECTION = No
    CONNECT_Z_MODE = First Wins
    CONSIDER_NODE_ELEVATION = no
    DEAGGREGATE_INPUT = Deaggregate
    DONUT_CREATION = Yes
    DROP_HOLES = No
    LINES_AS_SEGMENTS = No
    POLY_ACCUM_ATTRS_NAME = Use Attributes From One Feature
    SNAPTYPE_PARAM = None
    AREA -> DNOO_SH_SHALL_POLY (writer GEODATABASE_FILE_2)
    Incomplete -> LineCloser_2
    <REJECTED> -> closed_structboundary_err (writer CSV2_1)
LineCloser_2
    CONNECT_Z_MODE = First Wins
    AREA -> DNOO_SH_SHALL_POLY (writer GEODATABASE_FILE_2)
DNOO_SH_SHALL_POLY (writer GEODATABASE_FILE_2)
    attributes: GLOBALID char(38), BOUNDARYID double(22,0), CUSTTYPE double(22,0), DATE_LASTUPD date, DATE_TARGETEND date, DATE_TARGETSTART date, DEPT char(3), G3E_FID double(10,0), G3E_FNO integer, G3E_ID double(10,0), IPID double(22,0), JOBMODIFIED char(30), JOBPLACED char(30), LASTUPDBY char(20), LOCALNUM char(6), MAPNAME char(8), METERNUM double(22,0), OC char(2), OWNERCNO integer, OWNID double(22,0), PREMISNUM char(12), PROJSCH char(12), RB_STATE double(22,0), REMARKS char(30), SAPDESCRIPTION char(40), SAP_EQUIP_ID char(18), SAP_FUN_LOC_ID char(40), SAP_NULL_DATE date, SAP_POST_ID char(50), SEROWNID double(22,0),
      STATUS double(22,0), VOLTAGE char(3), TEXT char(1023), SHSHALLOW_REMARK char(32), CONVERSION_REMARKS char(4000)
DNOO_SH_STRUCT (reader ORACLE_SPATIAL_1)
    attributes: GLOBALID varchar2(38), BOUNDARYID number(22,0), CUSTTYPE number(22,0), DATE_LASTUPD date, DATE_TARGETEND date, DATE_TARGETSTART date, DEPT varchar2(3), G3E_FID number(10,0), G3E_FNO number(5,0), G3E_ID number(10,0), IPID number(22,0), JOBMODIFIED varchar2(30), JOBPLACED varchar2(30), LASTUPDBY varchar2(20), LOCALNUM varchar2(6), MAPNAME varchar2(8), METERNUM number(22,0), OC varchar2(2), OWNERCNO number(5,0), OWNID number(22,0), PREMISNUM varchar2(12), PROJSCH varchar2(12), RB_STATE number(22,0), REMARKS varchar2(30), SAPDESCRIPTION varchar2(40), SAP_EQUIP_ID varchar2(18), SAP_FUN_LOC_ID varchar2(40), SAP_NULL_DATE date, SAP_POST_ID varchar2(50), SEROWNID number(22,0),
      STATUS number(22,0), VOLTAGE varchar2(3), BACKFILLED varchar2(1), COMM_STATUS varchar2(1), CONFSPACE varchar2(1), DATE_COMM_D date, DATE_DECOMM_D date, DATE_FIRST_COMM_D date, FIREPROTECTION varchar2(1), FLOODFAC varchar2(1), FORCEVENTILATION varchar2(1), HEIGHTSTRUCT number, LENGTHSTRUCT number, LOCATION varchar2(60), STRUCTUREID varchar2(10), STRUCTURETYPE number(5,0), WIDTHSTRUCT number, TEXT varchar2(1023), CONVERSION_REMARKS varchar2(4000)
    -> AreaBuilder_3
AreaBuilder_3
    ALLOW_CYCLES = No
    CHECK_CURVE_DIRECTION = No
    CONNECT_Z_MODE = First Wins
    CONSIDER_NODE_ELEVATION = no
    DEAGGREGATE_INPUT = Deaggregate
    DONUT_CREATION = Yes
    DROP_HOLES = No
    LINES_AS_SEGMENTS = No
    POLY_ACCUM_ATTRS_NAME = Use Attributes From One Feature
    SNAPTYPE_PARAM = None
    AREA -> DNOO_SH_STRUCT_POLY (writer GEODATABASE_FILE_2)
    Incomplete -> LineCloser_3
    <REJECTED> -> closed_structboundary_err (writer CSV2_1)
LineCloser_3
    CONNECT_Z_MODE = First Wins
    AREA -> DNOO_SH_STRUCT_POLY (writer GEODATABASE_FILE_2)
DNOO_SH_STRUCT_POLY (writer GEODATABASE_FILE_2)
    attributes: GLOBALID char(38), BOUNDARYID double(22,0), CUSTTYPE double(22,0), DATE_LASTUPD date, DATE_TARGETEND date, DATE_TARGETSTART date, DEPT char(3), G3E_FID double(10,0), G3E_FNO integer, G3E_ID double(10,0), IPID double(22,0), JOBMODIFIED char(30), JOBPLACED char(30), LASTUPDBY char(20), LOCALNUM char(6), MAPNAME char(8), METERNUM double(22,0), OC char(2), OWNERCNO integer, OWNID double(22,0), PREMISNUM char(12), PROJSCH char(12), RB_STATE double(22,0), REMARKS char(30), SAPDESCRIPTION char(40), SAP_EQUIP_ID char(18), SAP_FUN_LOC_ID char(40), SAP_NULL_DATE date, SAP_POST_ID char(50), SEROWNID double(22,0),
      STATUS double(22,0), VOLTAGE char(3), BACKFILLED char(1), COMM_STATUS char(1), CONFSPACE char(1), DATE_COMM_D date, DATE_DECOMM_D date, DATE_FIRST_COMM_D date, FIREPROTECTION char(1), FLOODFAC char(1), FORCEVENTILATION char(1), HEIGHTSTRUCT double, LENGTHSTRUCT double, LOCATION char(60), STRUCTUREID char(10), STRUCTURETYPE integer, WIDTHSTRUCT double, TEXT char(1023), CONVERSION_REMARKS char(4000)
closed_structboundary_err (writer CSV2_1)
    attributes: G3E_FNO int64, G3E_CNO int64, G3E_FID int64

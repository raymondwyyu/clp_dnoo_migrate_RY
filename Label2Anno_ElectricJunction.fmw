FME workspace Label2Anno_ElectricJunction.fmw

Parameters:
- DestDataset_GEODATABASE_FILE = $(FME_MF_DIR)Test_RY1c.gdb   # File Geodatabase
- SourceDataset_ORACLE_SPATIAL = dnoo   # Connection
- DestDataset_CSV2 = E:\Temp\RY\Test_RY1   # Destination CSV (Comma Separated Value) Folder

Readers:
- ORACLE_SPATIAL_1: ORACLE_SPATIAL from $(SourceDataset_ORACLE_SPATIAL) in HongKong80b.GridSystem

Writers:
- GEODATABASE_FILE_3: GEODATABASE_FILE to $(DestDataset_GEODATABASE_FILE)
- CSV2_1: CSV2 to $(DestDataset_CSV2)

Note: NOTES: / For fontsize, font, annoclassid... / Do not set value to user parameter and then asssign to writer attribute; / Set direct value to a (temp) attribute then assign to writer attribute
null_text_ElectricJunction (writer CSV2_1)
    attributes: G3E_FNO int64, G3E_CNO int64, Total int64, G3E_FID int64
Note: ArcGIS Label to Anno, with attribute, alignment, annoClass
Note: ERROR: MISSING 5 SOURCE TABLEs
CountNull_2: Counter
    CNT_ATTR = _count
    DOMAIN = counter
    SCOPE = Global
    START = 1
TestFilter_2
    DEFAULT_VALUE = <UNFILTERED>
    PASSED_TEST_GROUP_OUTPUT = FIRST

Bookmark: HV Junction
ANNO_HV_JOINT_MISC (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> HV_Joint_Misc
ANNO_HV_JOINT_TYPE (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> HV_Joint_Type
ANNO_HV_TERM_MISC (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> HV_Term_Misc
ANNO_HV_TERM_PU (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> HV_Term_PU

Bookmark: ElectricLine Set Attr
HV_Joint_Misc: AttributeCreator
    ATTR_TABLE:
      SET_TO _anno_class_id = 1
      SET_TO _font_point_size = 4
      SET_TO _font_name = Courier New
    -> HV_color
HV_Joint_Type: AttributeCreator
    ATTR_TABLE:
      SET_TO _anno_class_id = 2
      SET_TO _font_point_size = 3
      SET_TO _font_name = Courier New
    -> HV_color
LV_Joint_Misc: AttributeCreator
    ATTR_TABLE:
      SET_TO _anno_class_id = 5
      SET_TO _font_point_size = 4
      SET_TO _font_name = Courier New
    -> LV_color
LV_Joint_Type: AttributeCreator
    ATTR_TABLE:
      SET_TO _anno_class_id = 6
      SET_TO _font_point_size = 3
      SET_TO _font_name = Courier New
    -> LV_color
LV_Non-CLP_Misc: AttributeCreator
    ATTR_TABLE:
      SET_TO _anno_class_id = 7
      SET_TO _font_point_size = 4
      SET_TO _font_name = Courier New
    -> LV_color
LV_Non-CLP_Term_Type: AttributeCreator
    ATTR_TABLE:
      SET_TO _anno_class_id = 8
      SET_TO _font_point_size = 4
      SET_TO _font_name = Courier New
    -> LV_color
LV_Term_Misc: AttributeCreator
    ATTR_TABLE:
      SET_TO _anno_class_id = 9
      SET_TO _font_point_size = 4
      SET_TO _font_name = Courier New
    -> LV_color
LV_Term_Type: AttributeCreator
    ATTR_TABLE:
      SET_TO _anno_class_id = 10
      SET_TO _font_point_size = 6
      SET_TO _font_name = Courier New
    -> LV_color
SH_PL_Controller_Misc: AttributeCreator
    ATTR_TABLE:
      SET_TO _anno_class_id = 11
      SET_TO _font_point_size = 6
      SET_TO _font_name = Courier New
    -> LV_color
SH_PL_Controller_Number: AttributeCreator
    ATTR_TABLE:
      SET_TO _anno_class_id = 12
      SET_TO _font_point_size = 6
      SET_TO _font_name = Courier New
    -> LV_color
SH_PL_Controller_Type: AttributeCreator
    ATTR_TABLE:
      SET_TO _anno_class_id = 13
      SET_TO _font_point_size = 6
      SET_TO _font_name = Courier New
    -> LV_color
TR_Cable_Point_Type: AttributeCreator
    ATTR_TABLE:
      SET_TO _anno_class_id = 14
      SET_TO _font_point_size = 6
      SET_TO _font_name = Courier New
    -> TR_color
TR_Joint_Term_Misc: AttributeCreator
    ATTR_TABLE:
      SET_TO _anno_class_id = 15
      SET_TO _font_point_size = 6
      SET_TO _font_name = Courier New
    -> TR_color
TR_JointType_InSub: AttributeCreator
    ATTR_TABLE:
      SET_TO _anno_class_id = 18
      SET_TO _font_point_size = 5
      SET_TO _font_name = Courier New
    -> TR_color
TR_JointType_OutSub: AttributeCreator
    ATTR_TABLE:
      SET_TO _anno_class_id = 19
      SET_TO _font_point_size = 7
      SET_TO _font_name = Courier New
    -> TR_color
HV_Term_Misc: AttributeCreator
    ATTR_TABLE:
      SET_TO _anno_class_id = 3
      SET_TO _font_point_size = 6
      SET_TO _font_name = Courier New
    -> HV_color
HV_Term_PU: AttributeCreator
    ATTR_TABLE:
      SET_TO _anno_class_id = 4
      SET_TO _font_point_size = 6
      SET_TO _font_name = Courier New
    -> HV_color
TR_Joint_Term_Misc_2: AttributeCreator
    ATTR_TABLE:
      SET_TO _anno_class_id = 16
      SET_TO _font_point_size = 6
      SET_TO _font_name = Courier New
    -> TR_color
TR_Joint_Term_Misc_3: AttributeCreator
    ATTR_TABLE:
      SET_TO _anno_class_id = 17
      SET_TO _font_point_size = 8
      SET_TO _font_name = Courier New
    -> TR_color

Bookmark: LV Devices
ANNO_LV_JOINT_MISC (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> LV_Joint_Misc
ANNO_LV_JOINT_TYPE (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> LV_Joint_Type
ANNO_LV_NONCLP_MISC (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> LV_Non-CLP_Misc
ANNO_LV_NONCLP_TERM_TYPE (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> LV_Non-CLP_Term_Type
ANNO_LV_TERM_MISC (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> LV_Term_Misc
ANNO_LV_TERM_TYPE (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> LV_Term_Type
ANNO_SH_PL_CONTROLLER_MISC (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> SH_PL_Controller_Misc
ANNO_SH_PL_CONTROLLER_NUMBER (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> SH_PL_Controller_Number
ANNO_SH_PL_CONTROLLER_TYPE (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> SH_PL_Controller_Type

Bookmark: color
LV_color: AttributeCreator
    ATTR_TABLE = SET_TO _color = 0,200,0
    -> Parent_existed
HV_color: AttributeCreator
    ATTR_TABLE = SET_TO _color = 0,0,200
    -> Parent_existed
TR_color: AttributeCreator
    ATTR_TABLE = SET_TO _color = 200,0,0
    -> Parent_existed

Bookmark: TR Devices
ANNO_TR_CABLE_POINT_TYPE (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> TR_Cable_Point_Type
ANNO_TR_JOINT_TERM_MISC (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(1023), ROTATION number, G3E_SIZE number, G3E_FONTNAME char(11)
    -> TR_Joint_Term_Misc
ANNO_TR_JOINTTYPE_INSUB (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(4000), ROTATION number, G3E_SIZE number, G3E_FONTNAME char(11)
    -> TR_JointType_InSub
ANNO_TR_JOINTTYPE_OUTSUB (reader ORACLE_SPATIAL_1)
    attributes: GLOBALID varchar2(4000), PARENT_UUID char(38), G3E_FNO number(5,0), G3E_CNO number(5,0), G3E_CID number(10,0), G3E_FID number(10,0), G3E_ID number(10,0), G3E_ALIGNMENT number(5,0), TEXT varchar2(4000), ROTATION number, G3E_SIZE number, G3E_FONTNAME char(11)
    -> TR_JointType_OutSub

Bookmark: Point to Annotation
Parent_existed: TestFilter
    DEFAULT_VALUE = Has
    PASSED_TEST_GROUP_OUTPUT = FIRST
    TEST_LIST = "BOOL_OP,OR,COMPOSITE_TEST,""""""1"""""",TEST_CLAUSE,TEST PARENT_UUID ATTRIBUTE_VALUE_NULL """,No
    Has -> v_align_2
GeometryValidator
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme CONSECUTIVE_IDENTICAL_VERTICES_2D CHECK_Z]YES]FME_CONTROLLER_QUERY_FILE]transformers/dependencies/geometryvalidator8/CONSECUTIVE_IDENTICAL_VERTICES_2D.fme MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme NULL_REMOVAL FME_CONTROLLER_QUERY_FILE]transformers/dependencies/geometryvalidator8/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme OGC_VALID_CHECK OGC_VERSION]V1.2.0]FME_CONTROLLER_QUERY_FILE]transformers/dependencies/geometryvalidator8/OGC_VALID_CHECK.fme PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers/dependencies/geometryvalidator8/PLANAR_SURFACE.fme SELF_INTERSECTING CHECK_HOLE_TOUCHING_POLYGON]No]CONNECT_Z_MODE_SI]FIRST_WINS]SELF_INTERSECTION_TOLERANCE]None]FME_CONTROLLER_QUERY_FILE]transformers/dependencies/geometryvalidator8/SELF_INTERSECTING.fme SHELL_VALIDATION FLIP_APPEARANCE_MODE]FLIP_APPEARANCES]FME_CONTROLLER_QUERY_FILE]transformers/dependencies/geometryvalidator8/SHELL_VALIDATION.fme SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]0.0]FME_CONTROLLER_QUERY_FILE]transformers/dependencies/geometryvalidator8/TYPE_REPAIR.fme MISMATCHED_DIMENSIONS FORCE_DIMENSION]2D]FME_CONTROLLER_QUERY_FILE]transformers/dependencies/geometryvalidator8/MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers/dependencies/geometryvalidator8/MISSING_MEASURES_AND_ELEVATIONS.fme SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> LabelPointReplacer
LabelPointReplacer
    ALWAYSROTATE = no
    HEIGHT = 7*0.352778
    LABATTR = @Value(TEXT)
    LabelPoint -> NullText_2
NullText_2: TestFilter
    DEFAULT_VALUE = NotNULL
    PASSED_TEST_GROUP_OUTPUT = FIRST
    TEST_LIST = "BOOL_OP,OR,COMPOSITE_TEST,""""""1"""""",TEST_CLAUSE,TEST TEXT ATTRIBUTE_VALUE_NULL """,NULL
    NULL -> StatisticsCalculator
    NotNULL -> TextPropertySetter_2
Note: alignment lookup / 10 bottom,right / 8 bottom,center / 9 bottom,left / 2 center,right / 0 center,center / 1 center,left / 6 top,right / 4 top,center / 5 top,left
TextPropertySetter_2
    TEXT_SIZE = 0
    -> ElectricJunction_Anno (writer GEODATABASE_FILE_3)
StatisticsCalculator
    CALCULATION_MODE = NUMERIC
    FEAT_STATS = G3E_CNO,NUMERIC_MODE,,,COUNT,,,,,,,,,,
    GROUP_BY = G3E_CNO
    COMPLETE -> null_text_ElectricJunction (writer CSV2_1)

Bookmark: alignment
v_align_2: AttributeValueMapper
    DEFAULT_VALUE = Top
    LUT = 0,Center,1,Center,2,Center,4,Top,5,Top,6,Top,8,Bottom,9,Bottom,10,Bottom
    MAPPING_DIRECTION = FORWARD
    SRC = G3E_ALIGNMENT
    VAL_ATTR = _v_align
    -> h_align_2
h_align_2: AttributeValueMapper
    DEFAULT_VALUE = Left
    LUT = 0,Center,1,Left,2,Right,4,Center,5,Left,6,Right,8,Center,9,Left,10,Right
    MAPPING_DIRECTION = FORWARD
    SRC = G3E_ALIGNMENT
    VAL_ATTR = _h_align
    -> GeometryValidator

Bookmark: Writer Feature Types
ElectricJunction_Anno (writer GEODATABASE_FILE_3)
    attributes: FeatureID integer, ZOrder integer, AnnotationClassID integer, SymbolID integer, Status smallint, TextString char(255), FontName char(255), FontSize double, Underline smallint, VerticalAlignment smallint, HorizontalAlignment smallint, XOffset double, YOffset double, Angle double, FontLeading double, WordSpacing double, CharacterWidth double, CharacterSpacing double, FlipAngle double, Override integer, SHAPE_Length double, SHAPE_Area double, FontStyle char(255), OBJECTID integer, ROTATION double, TEXT char(255), G3E_FID integer, G3E_FNO integer, G3E_CID integer, G3E_CNO integer,
      G3E_ID integer, G3E_ALIGNMENT integer, GLOBALID globalid, PARENT_UUID guid
